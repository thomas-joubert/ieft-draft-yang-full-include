module ietf-yang-full-embed-library {
  yang-version 1.1;
  namespace "urn:ietf:params:xml:ns:yang:ietf-yang-full-embed-library";
  prefix "emblib";

  import ietf-datastores {
    prefix ds;
    reference
      "RFC 8342: Network Management Datastore Architecture
      (NMDA)";
  }

  import ietf-yang-library {
    prefix yanglib;
    reference
      "RFC 8525: YANG Library";
  }

  import ietf-yang-types {
    prefix yang;
    reference
      "RFC 6991: Common YANG Data Types";
  }

  organization
    "IETF NETMOD (NETCONF Data Modeling Language) Working Group";


  contact
    "WG Web:   <https://datatracker.ietf.org/wg/netmod/>
    WG List:  <mailto:netmod@ietf.org>

    Editor:   ";

  description
    "This module augments the ietf-yang-library module to indicate
    which modules are available in each embedding point.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.

    Copyright (c) 2023 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX;
    see the RFC itself for full legal notices.";

  revision 2023-11-05 {
    description
      "Initial revision.";
    reference
      "RFC XXXX: YANG Full Embed";
  }

  augment /yanglib:yang-library {
    description "Add mapping for embedding points";
    list embedding-points {
      key "datastore embedding-path";
      description
        "Mapping of each embedding point to its schema. An
        embedding-point is defined by a datastore and a YANG
        path to the anydata node containing the embedded schema.";
      leaf datastore {
        type ds:datastore-ref;
        description
          "Identity of the datastore containing the embedding point";
      }
      leaf embedding-path {
        type yang:xpath1.0;
        description "Path to the embedding point in the datastore.
         The XPath must be an absolute path. It is evaluated in the
         context of the specified datastore.";
      }
      leaf schema {
        type leafref {
          path "../../yanglib:schema/yanglib:name";
        }
        mandatory true;
        description
          "A reference to the schema supported by the specified
           embedding point. All non-import modules of the schema are
           implemented in the given embedding point with their
           associated features and deviations.";
      }
    }
  }
}
